module migration {
  namespace "http://example.com/interface-migration";
  prefix interface-migration;

  import ietf-inet-types {
    prefix inet;
  }
  import tailf-common {
    prefix tailf;
  }
  import tailf-ncs {
    prefix ncs;
  }
  import ietf-yang-types {
    prefix types;
  }

  description
    "NSO Interface Migration Service - manages migration of interfaces 
     from source to target devices with state tracking";

  revision 2024-01-01 { 
    description
      "Initial revision for interface migration service";
  }

  // Define interface types
  typedef interface-type {
    type enumeration {
      enum "Bundle" {
        description "Bundle interface (e.g., Bundle-Ether, Port-channel)";
      }
      enum "Physical" {
        description "Physical interface (e.g., GigabitEthernet, TenGigE)";
      }
    }
    description "Interface type classification";
  }

  // Define interface states
  typedef interface-state {
    type enumeration {
      enum "a" {
        description "State A - Planning";
      }
      enum "b" {
        description "State B - Configured";
      }
      enum "c" {
        description "State C - Testing";
      }
      enum "d" {
        description "State D - Active";
      }
      enum "e" {
        description "State E - Decommissioned";
      }
    }
    description "Interface state options";
  }

  typedef mig-stage {
    tailf:info "Migration Stage";
    type enumeration {
      enum "planned" {
        description "Direct cutover migration";
      }
      enum "approved" {
        description "Parallel running migration";
      }
      enum "pre-migration" {
        description "Phased migration approach";
      }
      enum "pre-flight" {
        description "Phased migration approach";
      } 
      enum "in-progress" {
        description "Phased migration approach";
      }
      enum "migrated" {
        description "Phased migration approach";
      }            
      enum "monitoring" {
        description "Phased migration approach";
      }
      enum "failed" {
        description "Phased migration approach";
      } 
      enum "rolled-back" {
        description "Phased migration approach";
      }        
    }
    default "planned";
  }   

  list interface-migration {
    description "Interface migration batch configuration";
    key "batchID";

    uses ncs:service-data;
    ncs:servicepoint interface-migration-servicepoint;

    leaf batchID {
      tailf:info "Unique batch identifier for migration group";
      type string {
        pattern "[A-Za-z0-9_-]+";
        length "1..64";
      }
      description "Unique identifier for the migration batch";
    }

    leaf batch-stage {
      tailf:info "Migration Stage";
      type enumeration {
        enum "planned" {
          description "Direct cutover migration";
        }
        enum "approved" {
          description "Parallel running migration";
        }
        enum "pre-migration" {
          description "Phased migration approach";
        }
        enum "pre-flight" {
          description "Phased migration approach";
        } 
        enum "in-progress" {
          description "Phased migration approach";
        }
        enum "migrated" {
          description "Phased migration approach";
        }            
        enum "monitoring" {
          description "Phased migration approach";
        }
        enum "failed" {
          description "Phased migration approach";
        } 
        enum "rolled-back" {
          description "Phased migration approach";
        }        
      }
      default "planned";
    } 
//// start 

  list migrations {
    key "name";
    
    leaf name {
      type string;
      description "Interface name";
    }
    leaf description {
      type string;
      description "Interface Description";
    }
    leaf CRQ {
      type string;
      description "Change Request";
    } 

    leaf stage {
      type mig-stage;
      description "Stage of each component migration";
      mandatory true;
    } 


    // client Interface Configuration
    container client {  
      tailf:info "client / CSR interface configuration";
      description "Configuration for the CSR";

      leaf device {
        tailf:info "client device name";
        type string;
        mandatory true;
        description "client CSR (free text)";
      } 

      ///
      container connection-type {
       leaf interface-type {
         tailf:info "Source interface type (Bundle or Physical)";
          type interface-type;
          mandatory true;
          description "Type of client connection";
      }
            leaf name {
              type string;
              description "Name";
            }
            leaf description {
              type string;
              description "Description";
            }      
      }
    } // end client container

  
    container source {  
      tailf:info "source interface configuration";
      description "Configuration for the target interface being migrated to";

      leaf device {
        tailf:info "source device name";
        type leafref {
          path "/ncs:devices/ncs:device/ncs:name";
        }
        mandatory true;
        description "source device for interface migration";
      } 

      ///
      container connection-type {
        choice connection-type {
          case bundle {
            leaf bundle-name {
              type string;
              description "Bundle Name";
            }
            leaf bundle-description {
              type string;
              description "Bundle Description";
            }
            leaf bundle-state {
              type enumeration {
                enum "up" {
                  description "Bundle is UP";
                }
                enum "down" {
                  description "Bundle is DOWN";
                }                
              }
              description "Bundle state";
            }            
            list interfaces {
              key "name";
              max-elements 2;  // Only up to 2 interface entries allowed

              leaf name {
                type string;
                description "Interface name";
              }
              leaf description {
                type string;
                description "Interface Description";
              }
            }
          }

          case physical {
            list interface {
              key "name";
              max-elements 1;  // Only 1 interface entry allowed

              leaf name {
                type string;
                description "Interface name";
              }
              leaf description {
                type string;
                description "Interface Description";
              }
              leaf ip-address {
                type inet:ipv4-address;
                description "IPv4 address of the interface";
              }
              leaf state {
                type enumeration {
                  enum up;
                  enum down;
                }
                description "Administrative state of the interface";
              }
            }
          }
        }
      }
    } // end source container
 
    // Target Interface Configuration  
    container target {
      tailf:info "source interface configuration";
      description "Configuration for the target interface being migrated to";

      leaf device {
        tailf:info "target device name";
        type leafref {
          path "/ncs:devices/ncs:device/ncs:name";
        }
        mandatory true;
        description "target device for interface migration";
      } 

      ///
      container connection-type {
        choice connection-type {
          case bundle {
            leaf bundle-name {
              type string;
              description "Bundle Name";
            }
            leaf bundle-description {
              type string;
              description "Bundle Description";
            }
            list interfaces {
              key "name";
              max-elements 2;  // Only up to 2 interface entries allowed

              leaf name {
                type string;
                description "Interface name";
              }
              leaf description {
                type string;
                description "Interface Description";
              }
            }
          }

          case physical {
            list interface {
              key "name";
              max-elements 1;  // Only 1 interface entry allowed

              leaf name {
                type string;
                description "Interface name";
              }
              leaf description {
                type string;
                description "Interface Description";
              }
              leaf ip-address {
                type inet:ipv4-address;
                description "IPv4 address of the interface";
              }
              leaf state {
                type enumeration {
                  enum up;
                  enum down;
                }
                description "Administrative state of the interface";
              }
            }
          }
        }
      }
         // Validation and constraints
    //must "source/device != target/device or source/interface-name != target/interface-name" {
    //must "source/device != target/device" {
    //  error-message "source and target must be different (different device or different interface)";
    //}
    } // end target container
    must "source/device != target/device" {
      error-message "source and target must be different (different device or different interface)";
    }
 }    
///// end
    // Migration Metadata
    container migration-info {
      tailf:info "Migration process information";
      description "Additional information about the migration process";

      leaf migration-type {
        tailf:info "Type of migration being performed";
        type enumeration {
          enum "cutover" {
            description "Direct cutover migration";
          }
          enum "parallel" {
            description "Parallel running migration";
          }
          enum "phased" {
            description "Phased migration approach";
          }
        }
        default "cutover";
      }

      leaf priority {
        tailf:info "Migration priority level";
        type enumeration {
          enum "low" {
            description "Low priority migration";
          }
          enum "medium" {
            description "Medium priority migration";
          }
          enum "high" {
            description "High priority migration";
          }
          enum "critical" {
            description "Critical priority migration";
          }
        }
        default "medium";
      }

      leaf scheduled-date {
        tailf:info "Scheduled migration date (YYYY-MM-DD)";
        type types:date-and-time;
        description "Planned date for migration execution";
      }

      leaf maintenance-window {
        tailf:info "Maintenance window for migration";
        type string;
        description "Maintenance window details";
      }

      leaf created-by {
        tailf:info "User who created this migration batch";
        type string;
        description "Username of the person who created this migration";
      }

      leaf notes {
        tailf:info "Additional notes about the migration";
        type string {
          length "0..1000";
        }
        description "Free-form notes about the migration";
      }
    }

 

    // Operational data
    container status {
      //config true;
      tailf:info "Migration status information";
      description "Operational status of the migration";

      leaf current-status {
        type enumeration {
          enum "planned" {
            description "Migration is planned but not started";
          }
          enum "in-progress" {
            description "Migration is currently in progress";
          }
          enum "completed" {
            description "Migration completed successfully";
          }
          enum "failed" {
            description "Migration failed";
          }
          enum "rolled-back" {
            description "Migration was rolled back";
          }
        }
        description "Current status of the migration";
      }

      leaf last-updated {
        type string;
        description "Timestamp of last status update";
      }

      leaf completion-percentage {
        type uint8 {
          range "0..100";
        }
        units "percent";
        description "Migration completion percentage";
      }
    }
  }

  // RPC operations for migration management
  rpc execute-migration {
    tailf:info "Execute interface migration for specified batch";
    input {
      leaf batchID {
        type leafref {
          path "/interface-migration:interface-migration/interface-migration:batchID";
        }
        mandatory true;
        description "Batch ID to execute migration for";
      }

      leaf dry-run {
        type boolean;
        default false;
        description "Perform dry-run without actual changes";
      }
    }

    output {
      leaf result {
        type enumeration {
          enum "success" {
            description "Migration executed successfully";
          }
          enum "failure" {
            description "Migration execution failed";
          }
          enum "partial" {
            description "Migration partially completed";
          }
        }
        description "Execution result";
      }

      leaf message {
        type string;
        description "Detailed result message";
      }
    }
  }

  rpc rollback-migration {
    tailf:info "Rollback interface migration for specified batch";
    input {
      leaf batchID {
        type leafref {
          path "/interface-migration:interface-migration/interface-migration:batchID";
        }
        mandatory true;
        description "Batch ID to rollback migration for";
      }
    }

    output {
      leaf result {
        type enumeration {
          enum "success" {
            description "Rollback completed successfully";
          }
          enum "failure" {
            description "Rollback failed";
          }
        }
        description "Rollback result";
      }

      leaf message {
        type string;
        description "Detailed rollback message";
      }
    }
  }
}
